-- This MIB Generated by the JBoss MIB Generator

SIPCAPTURE-MODULE DEFINITIONS ::=BEGIN

IMPORTS
	OBJECT-TYPE,
	NOTIFICATION-TYPE,
	Counter32,
	Gauge32,
	Counter64,
	TimeTicks
		FROM SNMPv2-SMI
	DisplayString,
	TruthValue
		FROM SNMPv2-TC;

sipcapture:CORE		OBJECT IDENTIFIER ::= { 1 3 6 1 4 1 47235 9000 25 10 15 }
sipcapture:ALARMS		OBJECT IDENTIFIER ::= { 1 3 6 1 4 1 47235 9000 0 }
sipcapture:CORE		OBJECT IDENTIFIER ::= { 1 3 6 1 4 1 47235 9000 25 10 5 }
sipcapture:ALARMS		OBJECT IDENTIFIER ::= { 1 3 6 1 4 1 47235 9000 25 11 }
sipcapture:OS		OBJECT IDENTIFIER ::= { 1 3 6 1 4 1 47235 9000 25 }

hostname OBJECT-TYPE
	SYNTAX DisplayString
	ACCESS read-only
	STATUS current
	DESCRIPTION 
		"Hostname of the server"
::= { sipcapture:OS 1 }

uptime OBJECT-TYPE
	SYNTAX INTEGER
	ACCESS read-only
	STATUS current
	DESCRIPTION 
		"Uptime of the server."
::= { sipcapture:OS 2 }

loadAvg OBJECT-TYPE
	SYNTAX INTEGER
	ACCESS read-only
	STATUS current
	DESCRIPTION 
		"Load average of the server."
::= { sipcapture:OS 3 }

freeMem OBJECT-TYPE
	SYNTAX INTEGER
	ACCESS read-only
	STATUS current
	DESCRIPTION 
		"Free Memory of the server."
::= { sipcapture:OS 4 }

totalMem OBJECT-TYPE
	SYNTAX INTEGER
	ACCESS read-only
	STATUS current
	DESCRIPTION 
		"Total Memory of the server."
::= { sipcapture:OS 5 }

packetCount5m OBJECT-TYPE
	SYNTAX INTEGER
	ACCESS read-only
	STATUS current
	DESCRIPTION 
		"Packet Count @5m"
::= { sipcapture:CORE 1 }

packetSize5m OBJECT-TYPE
	SYNTAX INTEGER
	ACCESS read-only
	STATUS current
	DESCRIPTION 
		"Packet Size @5m"
::= { sipcapture:CORE 2 }

asr5m OBJECT-TYPE
	SYNTAX INTEGER
	ACCESS read-only
	STATUS current
	DESCRIPTION 
		"ASR @5m"
::= { sipcapture:CORE 3 }

ner5m OBJECT-TYPE
	SYNTAX INTEGER
	ACCESS read-only
	STATUS current
	DESCRIPTION 
		"NER @5m"
::= { sipcapture:CORE 4 }

packetCount15m OBJECT-TYPE
	SYNTAX INTEGER
	ACCESS read-only
	STATUS current
	DESCRIPTION 
		"Packet Count @15m"
::= { sipcapture:CORE 1 }

packetSize15m OBJECT-TYPE
	SYNTAX INTEGER
	ACCESS read-only
	STATUS current
	DESCRIPTION 
		"Packet Size @15m"
::= { sipcapture:CORE 2 }

asr15m OBJECT-TYPE
	SYNTAX INTEGER
	ACCESS read-only
	STATUS current
	DESCRIPTION 
		"ASR @15m"
::= { sipcapture:CORE 3 }

ner15m OBJECT-TYPE
	SYNTAX INTEGER
	ACCESS read-only
	STATUS current
	DESCRIPTION 
		"NER @15m"
::= { sipcapture:CORE 4 }

alarms5m OBJECT-TYPE
	SYNTAX INTEGER
	ACCESS read-only
	STATUS current
	DESCRIPTION 
		"Alarms @5m"
::= { sipcapture:ALARMS 5 }

alarms15m OBJECT-TYPE
	SYNTAX INTEGER
	ACCESS read-only
	STATUS current
	DESCRIPTION 
		"Alarms @15m"
::= { sipcapture:ALARMS 15 }

alarms30m OBJECT-TYPE
	SYNTAX INTEGER
	ACCESS read-only
	STATUS current
	DESCRIPTION 
		"Alarms @30m"
::= { sipcapture:ALARMS 30 }

alarms60m OBJECT-TYPE
	SYNTAX INTEGER
	ACCESS read-only
	STATUS current
	DESCRIPTION 
		"Alarms @60m"
::= { sipcapture:ALARMS 60 }

sipcapture.core:type=Alarms NOTIFICATION-TYPE
	OBJECTS {

		}
	STATUS current
	DESCRIPTION 
		""
::= { sipcapture:ALARMS 3 }

END
